module gcl {
  namespace urn:ieee:std:802.1Q:yang:ieee802-dot1q-sched;
  prefix sched;

  description
    "yang model for gate control list";

  container gate-parameter-table {
    description
      "A table that contains the per-port manageable parameters for
      traffic scheduling. For a given Port, an entry in the table
      exists. All writable objects in this table must be persistent
      over power up restart/reboot.";
    reference
      "12.29.1 of IEEE Std 802.1Q-2018
      8.6.8.4 of IEEE Std 802.1Q-2018
      8.6.9 of IEEE Std 802.1Q-2018";

    leaf port {
      type string;
      description
        "name of the port on which the gate control list is to be used ";
    }
    
    leaf queue-max-sdu {
      type uint32;
      default "0";
      description
        "The value of the queueMaxSDU parameter for the traffic
        class. A value of 0 is interpreted as the max SDU size
        supported by the underlying MAC. The value must be retained
        across reinitializations of the management system.
        On kontron switch there is currently only one setting for 
        all traffic classes ";
      reference
        "12.29.1.1.1 of IEEE Std 802.1Q-2018
        8.6.8.4 of IEEE Std 802.1Q-2018
        8.6.9 of IEEE Std 802.1Q-2018";
    }
      
    leaf gate-enabled {
      type boolean;
      default "false";
      description
        "The GateEnabled parameter determines whether traffic
        scheduling is active (true) or inactive (false). The value
        must be retained across reinitializations of the management
        system.
        tsntool qbvset --enable and --disable flag";
      reference
        "12.29.1 of IEEE Std 802.1Q-2018
        8.6.8.2 of IEEE Std 802.1Q-2018
        8.6.9.4.14 of IEEE Std 802.1Q-2018";
    }

    leaf admin-gate-states {
      type uint8;
      default "255";
      description
        "AdminGateStates is the administrative value of the initial
        gate states for the Port. The bits of the octet represent
        the gate states for the corresponding traffic classes; the
        most-significant bit corresponds to traffic class 7, the
        least-significant bit to traffic class 0. A bit value of 0
        indicates closed; a bit value of 1 indicates open. The value
        must be retained across reinitializations of the management
        system.
        tsntool qbvset --initgate flag ";
      reference
        "12.29.1 of IEEE Std 802.1Q-2018
        8.6.9.4.5 of IEEE Std 802.1Q-2018";
    }

    list gate-control-entry {
      key "index";
      leaf index {
        type uint32;
        description
          "The name (type) of the operation for this entry.";
      }

      leaf time-interval-value {
        type uint32;
        description
          "timeIntervalValue is a 32-bit unsigned integer,
          representing a number of nanoseconds. After timeIntervalValue
          nanoseconds have elapsed since the completion of the previous
          entry in the gate control list, control passes to the next
          entry.";
        reference
          "12.29.1.2.3 of IEEE Std 802.1Q-2018 8.6.8.4 of IEEE Std
          802.1Q-2018";
      }

      leaf gate-states-value {
        type uint8;
        mandatory true;
        description
          "gateStatesValue is the gate states for this entry for the
          Port. The gates are immediately set to the states in
          gateStatesValue when this entry executes. The bits of the
          octet represent the gate states for the corresponding
          traffic classes; the most-significant bit corresponds to
          traffic class 7, the least-significant bit to traffic class
          0. A bit value of 0 indicates closed; a bit value of 1
          indicates open.";
        reference
          "12.29.1.2.2 of IEEE Std 802.1Q-2018
          8.6.8.4 of IEEE Std 802.1Q-2018";
      }
    }

    container admin-cycle-time {
      description
        "Definition of a non-negative rational number.";
      leaf numerator {
        type uint32;
        description
          "Numerator of the rational number.";
      }
      leaf denominator {
        type uint32 {
          range "1..4294967295";
        }
        description
          "Denominator of the rational number.";
      }
    }

    leaf admin-cycle-time-extension {
      type uint32;
      units "nanoseconds";
      description
        "An unsigned integer number of nanoseconds, defining the
        maximum amount of time by which the gating cycle for the
        Port is permitted to be extended when a new cycle
        configuration is being installed. This is the administrative
        value.
        The value must be retained across reinitializations of the
        management system.";
      reference
        "12.29.1 of IEEE Std 802.1Q-2018
        8.6.9.4.4 of IEEE Std 802.1Q-2018";
    }

    container admin-base-time {
      description
        "The administrative value of the base time at which gating
        cycles begin, expressed as an IEEE 1588 precision time
        protocol (PTP) timescale.
        The PTP timestamp consists of 
        48-bit unsigned integer number of seconds and a 32-bit unsigned
        integer number of nanoseconds.
        ";
      reference
        "12.29.1 of IEEE Std 802.1Q-2018
        8.6.9.4.1 of IEEE Std 802.1Q-2018";
      leaf seconds {
        type uint64;
        description
          "This is the integer portion of the timestamp in units of
          seconds. The upper 16 bits are always zero.";
      }
      leaf nanoseconds {
        type uint32;
        description
          "This is the fractional portion of the timestamp in units of
          nanoseconds. This value is always less than 10^9.";
      }
    }

    leaf config-change {
      type boolean;
      description
        "The ConfigChange parameter signals the start of a
        configuration change when it is set to TRUE, indicating that
        the administrative parameters for the Port are ready to be
        copied into their corresponding operational parameters. This
        should only be done when the various administrative
        parameters are all set to appropriate values.";
      reference
        "12.29.1 of IEEE Std 802.1Q-2018
        8.6.9.4.7 of IEEE Std 802.1Q-2018";
    }
  }
}
